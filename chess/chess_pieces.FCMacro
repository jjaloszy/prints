import FreeCAD
import PartDesign
import random
import math

docname = 'document'

# Helper function to add and return the given object
def create_object(doc,type,name):
	doc.addObject(type,name)
	return doc.getObject(name)

# Create a queen object.  She will be a twisted spiraling hexagon
def create_queen(doc,height,base_radius,top_radius):
	doc.addObject('PartDesign::Body','Queen')
	queen = doc.getObject('Queen')

	z_inc = 0.5
	prisms = int(height / z_inc)
	for prism_number in range(0,prisms):
		prism_name = 'QueenPrism' + str(prism_number)
		doc.addObject('PartDesign::AdditivePrism',prism_name)
		prism = doc.getObject(prism_name)
		prism.Polygon=5
		proportion_up = float(prisms - prism_number)/prisms
		radius = proportion_up * base_radius + (1.0 - proportion_up) * top_radius
		prism.Circumradius=radius
		prism.Height=z_inc
		prism.FirstAngle=0.00
		prism.SecondAngle=0.0
		z = z_inc*prism_number
		rotation = z*2
		prism.Placement = FreeCAD.Placement(FreeCAD.Vector(0, 0, z), FreeCAD.Rotation(rotation,0,0))
		queen.addObject(prism)

def bishop_radius_proportion(height_proportion):
	a = 9.9999999999999512e-001
	b = -3.4286904761903845e+000
	c = 5.1946428571426413e+000
	d = -2.7559523809522513e+000
	h = height_proportion
	return a + h*b+h*h*c+h*h*h*h*d
	

# Create a  bishop object.
def create_bishop(doc, height, base_radius):
	bishop = create_object(doc, 'PartDesign::Body','Bishop')
	z_inc = 0.3
	prisms = int(height / z_inc)
	for prism_number in range(0,prisms):
		prism = create_object(doc, 'PartDesign::AdditivePrism', 'BishopBodyPrism' + str(prism_number))
		prism.Polygon = 5
		proportion_up = float(prisms - prism_number)/prisms
		radius = bishop_radius_proportion(proportion_up) * base_radius
		prism.Circumradius=radius
		prism.Height=z_inc
		prism.FirstAngle=0.0
		prism.SecondAngle=0.0
		z = z_inc*prism_number
		rotation = 0
		prism.Placement = FreeCAD.Placement(FreeCAD.Vector(0, 0, z), FreeCAD.Rotation(rotation,0,0))
		bishop.addObject(prism)

	jewel_max_radius = 7
	jewel_min_prism = int(0.2*prisms)
	jewel_max_prism = int(0.7*prisms)
	jewel_prism_range = float(jewel_max_prism - jewel_min_prism)
	jewel_largest_prism = (jewel_min_prism + jewel_max_prism) / 2
	for prism_number in range(jewel_min_prism, jewel_max_prism):
		prism = create_object(doc, 'PartDesign::AdditivePrism', 'BishopJewelPrism' + str(prism_number))
		prism.Polygon = 10
		jewel_proportion = (prism_number - jewel_min_prism) / jewel_prism_range
		if jewel_proportion > 0.5: 
			jewel_proportion = 0.5 - (jewel_proportion-0.5)

		radius = jewel_max_radius * jewel_proportion * 2 + 0.1
		print(radius)
		prism.Circumradius=radius
		prism.Height=z_inc
		prism.FirstAngle=0.0
		prism.SecondAngle=0.0
		z = z_inc*prism_number
		rotation = 0
		prism.Placement = FreeCAD.Placement(FreeCAD.Vector(0, 0, z), FreeCAD.Rotation(rotation,0,0))
		bishop.addObject(prism)

	


# create a base
def create_base(doc, step_height):
	doc.addObject('PartDesign::Body','BaseBody')
	base_body = doc.getObject('BaseBody')
	height = step_height
	for base_radius in [10,9,8]:
		base_name = 'base' + str(base_radius)
		doc.addObject('PartDesign::AdditiveCylinder',base_name)
		base = doc.getObject(base_name)
		base.Radius = base_radius
		base.Height = height
		base_body.addObject(base)
		height = height + step_height
	return base_body

# Washington monument-like king
def create_king(doc,height):
	width_0 = 11
	width_1 = 8
	top_height=10.0
	doc.addObject('PartDesign::Body','King')
	king = doc.getObject('King')

	bottom_name = 'KingBottom'
	doc.addObject('PartDesign::AdditiveWedge', bottom_name);
	bottom = doc.getObject(bottom_name)
	bottom.Ymax =height-top_height

	bottom.Xmin=-width_0/2
	bottom.Xmax=width_0/2
	bottom.Zmin=-width_0/2
	bottom.Zmax=width_0/2

	bottom.X2min=-width_1/2
	bottom.X2max=width_1/2
	bottom.Z2min=-width_1/2
	bottom.Z2max=width_1/2

	bottom.Placement = FreeCAD.Placement(FreeCAD.Vector(0, 0, 0), FreeCAD.Rotation(0,0,90))
	king.addObject(bottom)

	top_name = 'KingTop'
	doc.addObject('PartDesign::AdditiveWedge', top_name);
	top = doc.getObject(top_name)
	top.Support = [bottom,'Face4']
	top.AttachmentOffset = FreeCAD.Placement(FreeCAD.Vector(0, 0, 0), FreeCAD.Rotation(0,0,90))
	top.MapMode = 'InertialCS'

	top.Ymax = top_height

	top.Xmin=-width_1/2
	top.Xmax=width_1/2
	top.Zmin=-width_1/2
	top.Zmax=width_1/2

	top.X2min=0
	top.X2max=0
	top.Z2min=0
	top.Z2max=0

	king.addObject(top)
	
	height = 2.0
	for base_radius in [10,9,8]:
		base_name = 'base' + str(base_radius)
		doc.addObject('PartDesign::AdditiveCylinder',base_name)
		base = doc.getObject(base_name)
		base.Radius = base_radius
		base.Height = height
		king.addObject(base)

		height = height + 2.0

# Create the rook
def create_rook(doc, height):
	random.seed(123)
	layer_height = 2.0
	rook_name = 'Rook'
	doc.addObject('PartDesign::Body',rook_name)
	rook = doc.getObject(rook_name)
	faces = 4
	bottom_radius = 8.0
	top_radius = 4.0
	z = 0
#                                          0,1, 2,3,4,5,6,7,8,9,0,1,2,3,4,5,6,7,8,9
	radius_deviations = [2,2,1,2,1,0,1,0,1,0,1,0,1,0,1,2,1,2,1,0,-2]
	layer_number = 0
	while z < height: 
		layer_name = 'RookLevel' + str(layer_number)
		doc.addObject('PartDesign::AdditivePrism',layer_name)
		layer = doc.getObject(layer_name)

		z = layer_number*layer_height
		proportion_up = z/height
		smooth_radius = bottom_radius*(1-proportion_up) + top_radius*proportion_up			
		radius = smooth_radius + radius_deviations[layer_number]

		layer.Polygon=faces
		layer.Circumradius=radius
		layer.Height=layer_height
		layer.FirstAngle=0.00
		layer.SecondAngle=0.0
		rotation = random.random()*360.0
		layer.Placement = FreeCAD.Placement(FreeCAD.Vector(0, 0, z), FreeCAD.Rotation(rotation,0,0))
		rook.addObject(layer)	

		layer_number = layer_number+1


# return x,y,z of the knight at the given proportion
def knight_pos(height, width, prop):
	radius = height / 2.0
	radians = prop * 2*math.pi
	x = math.sin(radians) * width/2
	z_rel = -math.cos(radians)  * height/2
	center_z = height /2
	z = z_rel + center_z
	height_prop = z/height

	# At 0,2.  1/2,-5.  1,5
	y = 16*height_prop*height_prop - 16*height_prop + 2 

	return (x,y,z)

def knight_rot(height,width,prop):
	epsilon = 0.0001
	(x1,y1,z1) = knight_pos(height,width,prop-epsilon)
	(x2,y2,z2) = knight_pos(height,width,prop+epsilon)
	dx = x2-x1
	dy = y2-y1
	dz = z2-z1
	hyp = math.sqrt(dx*dx+dy*dy+dz*dz)

	if dz > 0 and dx < 0:
		return math.asin(dz/hyp)
	if dz > 0 and dx > 0:
		return math.acos(-dx/hyp)
	return math.acos(dx/hyp)

#	if dz > 0 and dx < 0:
#		return math.asin(dz/hyp) #
#	if dz > 0 and dx > 0: 
#		return -math.asin(dz/hyp) - math.pi/4
#	if dx < 0 and dx < 0:
#		return math.asin(dz/hyp) #
#	return -math.asin(dz/hyp) - math.pi/4

#	return asin

def knight_rot_axis(height,width,prop):
	epsilon = 0.0001
	(x1,y1,z1) = knight_pos(height,width,prop-epsilon)
	(x2,y2,z2) = knight_pos(height,width,prop+epsilon)
	dx = x2-x1
	dy = y2-y1
	dz = z2-z1
	return  FreeCAD.Vector(dx,dy,dx)


# Create a knight object.  She will be a twisted spiraling hexagon
def create_knight(doc,height,width,side):
	loop_name = 'Loop'
	doc.addObject('PartDesign::Body',loop_name)
	loop = doc.getObject(loop_name)

	iterations = 130
	iteration = 0
	for iteration in range(0,iterations):
		prop = iteration * 1.0 / iterations
		box_name = 'Box' + str(iteration)
		#doc.addObject('PartDesign::AdditivePrism',layer_name)
		doc.addObject('PartDesign::Box',box_name)
		box = doc.getObject(box_name)
		box.Length = side /8
		box.Width = side
		box.Height = side
		(x,y,z) = knight_pos(height, width, prop)
		location = FreeCAD.Vector(x, y, z)
		center = FreeCAD.Vector(box.Length/2, box.Width/2, box.Height/2)

		twist = (0.5-abs(prop-0.5)) * 90
		
		incline = knight_rot(height,width,prop)/math.pi*180
#		rotation = FreeCAD.Rotation(knight_rot_axis(height,width,prop), twist)
		box.Placement = FreeCAD.Placement(location, FreeCAD.Rotation(0,incline,twist),center)
#		box.Placement = FreeCAD.Placement(location, rotation,center)

		loop.addObject(box)
	base = create_base(doc, 2.0)
	base.Placement = App.Placement(App.Vector(0.00,4.00,-5.00),App.Rotation(App.Vector(0.00,0.00,1.00),0.00))
	knight = create_object(doc, 'PartDesign::Boolean','Knight')
	knight.addObjects([base,loop])
		

#create_queen(FreeCAD.ActiveDocument, 65, 10,1)
#create_king(FreeCAD.ActiveDocument, 65)
#create_rook(FreeCAD.ActiveDocument, 40)
#create_knight(FreeCAD.ActiveDocument, 30,18,7)
create_bishop(FreeCAD.ActiveDocument, 50, 10)



FreeCAD.ActiveDocument.recompute()
